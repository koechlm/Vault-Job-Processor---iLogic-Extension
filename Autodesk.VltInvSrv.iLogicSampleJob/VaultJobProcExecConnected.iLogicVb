AddReference "QuickstartiLogicLibrary.dll"
AddReference "Autodesk.Connectivity.WebServices.dll"
AddReference "Autodesk.DataManagement.Client.Framework.Vault.dll"
'DISCLAIMER:
'---------------------------------
'In any case, code, templates, and snippets of this solution are of "work in progress" character.
'Neither Markus Koechl, nor Autodesk represents that these samples are reliable, accurate, complete, or otherwise valid. 
'Accordingly, those configuration samples are provided “as is” with no warranty of any kind and you use the applications at your own risk.

Sub Main

'to enable iLogicVault commands reuse the job processor's user connection
	Dim iLogicVault As New QuickstartiLogicLibrary.QuickstartiLogicLib
	Dim LoggedIn As Boolean
	Dim FileState As String
	Try
		dbServer = RuleArguments("ServerName")
		fServer = RuleArguments("ServerName")
		vltName = RuleArguments("VaultName")
		userId = RuleArguments("UserId")
		ticket = RuleArguments("Ticket")
		LoggedIn = iLogicVault.ReuseConnection(dbServer, fServer, vltName, userId, ticket)
		FileState = RuleArguments("VaultRevisionState")
	Catch
	End Try
	
	If LoggedIn = False
		Dim ex As New Exception
		Logger.Error("Rule could not re-use Job Processor's Vault Login.")
		Throw ex
		Exit Sub
	End If
	
	Dim mExtRuleDirs As String
	For Each mDir As String In iLogicVb.Automation.FileOptions.ExternalRuleDirectories
			mExtRuleDirs += vbCr & mDir
	Next
		
	Logger.Info("iLogic External Rule Directories: " &  mExtRuleDirs)
	Logger.Info("iLogic Addin DLLs Directory: " & iLogicVb.Automation.FileOptions.AddinDirectory)
	Logger.Info("iLogic Loglevel set by Vault Job: " & iLogicVb.Automation.LogControl.Level)
	
	'use known iLogic syntax and snippets in job processor rules like you do in Inventor application rules
	iProperties.Value("Custom", "DateTimeStamp") = "JobProcessorTestRuleSuccess: " & DateTime.Now.ToString("yyyy/MM/dd HH:mm:ss")

	'Note - Vault Inventor Server uses a subset of the Inventor API. Use the Inventor Server object istead of Inventor Application.
	Dim mInvSrv As InventorServer = ThisServer
	
	'access the active document
  	Dim oDoc As Document = ThisDoc.Document	
	
End Sub
